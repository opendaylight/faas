/*
 * Copyright (c) 2015 Huawei Technologies and others.  All rights reserved.
 *
 * This program and the accompanying materials are made available under the
 * terms of the Eclipse Public License v1.0 which accompanies this distribution,
 * and is available at http://www.eclipse.org/legal/epl-v10.html
 */
module faas-ports {
    namespace "urn:opendaylight:faas:logical:faas-ports";
    prefix "faas-ports";

    import faas-common { prefix faas-common; }
    import ietf-yang-types { prefix "yang"; revision-date 2013-07-15; }
    import ietf-inet-types { prefix inet; revision-date 2013-07-15; }

    revision 2015-10-13 {
        description "Initial revision";
    }

    grouping port-location-attributes {
        description "The location of the port";
        leaf location-id {
            description "The entity id that this port is attached to";
            type faas-common:uuid;
        }
        leaf location-type {
            type enumeration {
                enum endpoint-type {
                    description "Endpoint.";
                }
                enum subnet-type {
                    description "Subnet.";
                }
                enum switch-type {
                    description "Layer 2 switch.";
                }
                enum router-type {
                    description "Layer 3 Router.";
                }
            }
        }
    }

    grouping ports-container {
        container ports {
            list port {
                key "uuid";
                uses faas-common:base-attributes;
                uses faas-common:admin-attributes;
                uses port-location-attributes;
                leaf edge-id {
                    type faas-common:uuid;
                }
                leaf-list security-rules-groups {
                    description "The rule groups that need to be applied to this port";
                    type faas-common:uuid;
                }
                leaf is-public {
                    description "True if accessed by the Internet";
                    type boolean;
                }
                leaf-list public-ips {
                    description "The public IP addresses, if any";
                    type inet:ip-address;
                }
                leaf mac-address {
                    type yang:mac-address;
                }
                list private-ips {
                    key subnet-id;
                    leaf subnet-id {
                        type faas-common:uuid;
                    }
                    leaf ip-address {
                        type inet:ip-address;
                    }
                }
            }
        }
    }
}
