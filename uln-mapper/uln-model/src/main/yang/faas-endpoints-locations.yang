/*
 * Copyright (c) 2015 Huawei Technologies and others.  All rights reserved.
 *
 * This program and the accompanying materials are made available under the
 * terms of the Eclipse Public License v1.0 which accompanies this distribution,
 * and is available at http://www.eclipse.org/legal/epl-v10.html
 */
module faas-endpoints-locations {
    namespace "urn:opendaylight:faas:logical:faas-endpoints-locations";
    prefix "faas-endpoints-locations";

    import faas-common { prefix faas-common; }
    import opendaylight-inventory { prefix inv; revision-date "2013-08-19"; }

    revision 2015-10-13 {
        description "Initial revision";
    }

    grouping endpoints-locations-container {
        container endpoints-locations {
            list endpoint-location {
                key "uuid";
                uses faas-common:base-attributes;
                leaf port {
                    description "The port connected to this endpoint location";
                    type faas-common:uuid;
                }
                leaf original-port-name {
                    description "the original port name such as neutron name";
                    type faas-common:text;
                }
                leaf node-id {
                    description "The switch for this attached endpoint";
                    type inv:node-id;
                }
                leaf node-connector-id {
                    description "The switch connector that this endpoint is attached to";
                    type inv:node-connector-id;
                }
            }
        }
    }
}
