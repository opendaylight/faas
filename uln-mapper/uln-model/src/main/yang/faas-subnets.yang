/*
 * Copyright (c) 2015 Huawei Technologies and others.  All rights reserved.
 *
 * This program and the accompanying materials are made available under the
 * terms of the Eclipse Public License v1.0 which accompanies this distribution,
 * and is available at http://www.eclipse.org/legal/epl-v10.html
 */
module faas-subnets {
    namespace "urn:opendaylight:faas:logical:faas-subnets";
    prefix "faas-subnets";

    import faas-common { prefix faas-common; }
    import ietf-inet-types { prefix inet; revision-date 2013-07-15; }

    revision 2015-10-13 {
        description "Initial revision";
    }

    grouping subnets-container {
        container subnets {
            list subnet {
                key "uuid";
                uses faas-common:logical-entity-attributes;
                leaf ip-prefix {
                    description "The IP prefix that defines the subnet";
                    type inet:ip-prefix;
                }
                leaf enable-dhcp {
                    type boolean;
                    description "Specifies whether DHCP is enabled for this subnet or not.";
                    default "true";
                }
                leaf-list dns-nameservers {
                    type inet:ip-address;
                    description "DNS name servers used by hosts in this subnet.";
                }
                leaf virtual-router-ip {
                    description "IP address to use for a virtual gateway router for the subnet,
                                        if desired.";
                    type inet:ip-address;
                }
                list external-gateways {
                    description "External gateways for subnets we serve, includes prefixes for
                                        static routing";
                    key "external-gateway";
                    leaf external-gateway {
                        type inet:ip-address;
                    }
                    leaf-list prefixes {
                        type inet:ip-prefix;
                    }
                }
            }
        }
    }
}
