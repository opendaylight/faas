module fabric-vxlan-rendered-mapping {

    yang-version 1;
    namespace "urn:opendaylight:faas:vxlan:rendered:mapping";
    prefix mapping;

    import ietf-inet-types { prefix "inet"; revision-date "2013-07-15"; }
    import fabric { prefix fabric; revision-date "2015-09-30"; }
    import fabric-types { prefix fabrictype; revision-date "2015-09-30"; }
    import network-topology {prefix topo; revision-date "2013-10-21"; }
    import ietf-yang-types { prefix "yang"; revision-date "2013-07-15"; }
    import ietf-access-control-list { prefix acl; revision-date "2016-02-18"; }
    import yang-ext { prefix "ext"; revision-date "2013-07-09"; }

    description
        "This module contains a collection of YANG definitions for Fabric.";

    revision "2015-09-30" {
        description
            "Initial revision of faas.";
    }

    container fabric-rendered-mapping {
        list fabric {
            key "id";
            leaf id {
                type fabric:fabric-id;
            }

            list vni-members {
                key vni;
                leaf vni {
                    type uint32;
                }
                list members {
                    key vtep;
                    leaf vtep {
                        type inet:ip-address;
                    }
                }
            }

            list acls {
                key vni;
                leaf vni {
                    type uint32;
                }
                uses fabrictype:acl-list;
            }

            list host-route {
                key "vni ip";
                leaf mac {
                    type yang:mac-address;
                }
                leaf vni {
                    type uint32;
                }
                leaf ip {
                    type inet:ip-address;
                }
                leaf dest-vtep {
                    type inet:ip-address;
                }
                leaf dest-tp-port {
                    type topo:tp-id;
                }
                leaf access-type {
                    type fabrictype:access-type;
                }
                leaf access-tag {
                    type uint32;
                }
            }
            list rib {
                key "vrf";

                leaf vrf {
                    type uint32;
                }

                uses fabrictype:route-group {
                    augment "route" {
                        ext:augment-identifier "vxlan-route-aug";
                        leaf outgoing-vni {
                            type uint32;
                        }
                    }
                }
            }
        }
    }
}
