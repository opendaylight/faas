module fabric-vxlan-device-adapter {

    yang-version 1;
    namespace "urn:opendaylight:faas:fabric:device:adapter:vxlan";
    prefix vxlan-adapter;

    import network-topology { prefix "topo"; revision-date "2013-10-21"; }
    import ietf-inet-types { prefix "inet"; revision-date "2013-07-15"; }
    import fabric-capable-device { prefix "device"; revision-date "2015-09-30"; }
    import fabric-types { prefix fabrictype; revision-date "2015-09-30"; }
    import yang-ext { prefix "ext"; revision-date "2013-07-09"; }

    description
        "This module contains the config model for vxlan capable fabric devices.";

    revision "2015-09-30" {
        description
            "Initial revision of faas.";
    }

    augment "/topo:network-topology/topo:topology/topo:node/device:attributes" {
        ext:augment-identifier "vtep-attribute";
        container vtep {
            leaf tp-id {
                type topo:tp-ref;
            }
            leaf ip {
                type inet:ip-address;
            }
        }
    }

    augment "/topo:network-topology/topo:topology/topo:node/device:config/device:bridge-domain" {

        leaf vni {
            type uint32;
        }
    }

    rpc addToVxlanFabric {
        input {
            leaf node-id {
                type instance-identifier;
                ext:context-reference "device:fabric-capable-device-context";
            }
            leaf fabric-id {
                type topo:node-id;
            }
        }
    }

    rpc rmFromVxlanFabric {
        input {
            leaf node-id {
                type instance-identifier;
                ext:context-reference "device:fabric-capable-device-context";
            }
            leaf fabric-id {
                type topo:node-id;
            }
        }
    }
}
