module fabric-types {

    yang-version 1;
    namespace "urn:opendaylight:faas:fabric:type";
    prefix fabrictypes;

    import ietf-inet-types { prefix "inet"; revision-date "2013-07-15"; }
    import network-topology { prefix "topo"; revision-date "2013-10-21"; }
    import ietf-yang-types { prefix "yang"; revision-date "2013-07-15"; }
    import ietf-access-control-list { prefix acl; revision-date "2016-02-18"; }

    description
        "This module contains a collection of YANG definitions for Fabric.";

    revision "2015-09-30" {
        description
            "Initial revision of faas.";
    }

    identity fabric-type {
    }

    identity vxlan-fabric {
        base fabric-type;
    }

    identity vlan-fabric {
        base fabric-type;
    }

    typedef service-capabilities { 
        type enumeration {
            enum ip-mapping;
            enum acl-redirect;
            enum dynamic-route-exchange;
        }
    }

    /*
     * Typedefs
     */
    typedef node-ref {
        description "A reference to a node in topology";
        type instance-identifier;
    }

    typedef tp-ref {
        description "A reference to a termination point in topology";
        type instance-identifier;
    }

    typedef link-ref {
        description "A reference to a link in topology";
        type instance-identifier;
    }

    typedef device-role {
        description "device role type";
        type enumeration {
            enum SPINE {
                description "";
            }
            enum LEAF {
                description "";
            }
            enum BORDER {
                description "";
            }
        }
        default "LEAF";
    }

    typedef fabric-port-role {
        description "the role of the physical port ";
        type enumeration {
            enum internal {
                description "the port used for devices to access each other.";
            }
            enum external {
                description "the port used for fabric to access outside network.";
            }
            enum access {
                description "the port used for Endpoint to access fabric.";
            }
            enum reserved {
                description " not decided yet. ";
            }
        }
    }

    typedef fabric-port-type {
        type enumeration {
            enum layer2interface {
            }
            enum layer3interface {
            }
            enum layer2Tunnel {
            }
            enum layer3Tunnel {
            }
        }
    }

    typedef underlayer-network-type {
        description "";
        type enumeration {
            enum VXLAN {
                description "";
            }
            enum TRILL {
                description "";
            }
            enum VLAN {
                description "";
            }
        }
    }

    typedef layer2-protocol-type-enum {
        description "";
        type enumeration {
            enum VLAN;
            enum VXLAN;
            enum TRILL;
            enum NvGRE;
        }
    }

    typedef access-type {
        description "";
        type enumeration {
            enum exclusive;
            enum vlan;
        }
    }

    grouping fabric-port {
        leaf name {
            type string;
        }
        leaf role {
            type fabric-port-role;
        }
        leaf type {
            type fabric-port-type;
        }
        leaf device-port {
            type tp-ref;
        }
        choice tunnel-option {
            case gre {
                 leaf src-ip {
                    type inet:ip-prefix;
                }
                leaf dest-ip {
                    type inet:ip-address;
                }
            }
        }
    }
    
    grouping acl-list {
        list fabric-acl {
            key fabric-acl-name;
            leaf fabric-acl-name {
                type string;
            }
        }
    }

    grouping logical-switch {
        leaf lsw-uuid {
            type yang:uuid;
        }
        leaf name {
            type string;
        }
        leaf segment-id {
            type uint32;
        }
        leaf network {
            type inet:ip-prefix;
        }
        leaf external {
            type boolean;
        }
        uses acl-list;
    }

    grouping logical-router {
        leaf lr-uuid {
            type yang:uuid;
        }
        leaf name {
            type string;
        }
        leaf vrf-ctx {
            type uint32;
        }

        uses acl-list;

		container routes {
        	uses route-group;
      	}
    }

    grouping logical-port {
        leaf lport-uuid {
            type yang:uuid;
        }
        leaf name {
            type string;
        }
        container port-layer {
            container layer-1-info {
                leaf location {
                    type topo:tp-id;
                }
            }
            container layer-2-info {
                leaf access-type {
                    type access-type;
                }
                leaf access-segment {
                    type uint32;
                }
            }
            container layer-3-info {
                leaf ip {
                    type inet:ip-address;
                }
                leaf network {
                    type inet:ip-prefix;
                }
                leaf mac {
                    type yang:mac-address;
                }
                leaf forward-enable {
                    type boolean;
                }
                leaf logical-switch {
                    type topo:node-id;
                }
            }
        }

        uses acl-list;
        uses port-functions;

        list underlayer-ports {
            key port-ref;
            leaf port-ref {
                type instance-identifier;
            }
        }
    }

    grouping logical-link {
    }

    grouping route-group {
        list route {
            key "destination-prefix";

            leaf description {
                type string;
                description "Textual description of the route.";
            }
            leaf destination-prefix {
                type inet:ipv4-prefix;
                mandatory true;
                description "IPv4 destination prefix.";
            }
            choice next-hop-options {
                case simple-next-hop {
                    leaf next-hop {
                        type inet:ipv4-address;
                        description "IPv4 address of the next hop.";
                    }
                    leaf outgoing-interface {
                        type topo:tp-id;
                        description "Name of the outgoing interface.";
                    }
                }
            }
        }
    }

    grouping port-functions {
        container port-function {
            choice function-type {
                case ip-mapping {
                    list ip-mapping-entry {
                        key "external-ip";
                        leaf external-ip {
                            type inet:ipv4-address;
                        }
                        leaf internal-ip {
                            type inet:ipv4-address;
                        }
                    }
                }
            }
        }
    } 

    augment "/acl:access-lists/acl:acl/acl:access-list-entries/acl:ace/acl:actions/acl:packet-handling" {
        case redirect {
            choice redirect-type {
                case tunnel {
                    choice tunnel-type {
                        case nsh {
                            leaf dest-ip {
                                type inet:ip-address;
                            }
                            leaf dest-port {
                                type inet:port-number;
                            }
                            leaf nsi {
                                type uint8;
                            }
                            leaf nsp {
                                type uint32;
                            }
                        }
                    }
                }
            }
        }
    }
}
