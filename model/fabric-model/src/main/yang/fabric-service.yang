module fabric-service {

    yang-version 1;
    namespace "urn:opendaylight:faas:fabric:services";
    prefix fabric-services;

    import network-topology { prefix "topo"; revision-date "2013-10-21"; }
    import ietf-inet-types { prefix "inet"; revision-date "2013-07-15"; }
    import yang-ext { prefix "ext"; revision-date "2013-07-09"; }
    import fabric-types { prefix fabrictype; revision-date "2015-09-30"; }
    import fabric { prefix fabric; revision-date "2015-09-30"; }
    import ietf-access-control-list { prefix acl; revision-date "2016-02-18"; }

    description
        "This module contains a collection of YANG definitions for Fabric.";

    revision "2015-09-30" {
        description
            "Initial revision of faas.";
    }

    augment "/topo:network-topology/topo:topology/topo:node" {
        description "Augmentation for logic switch nodes provided by faas.";

        ext:augment-identifier "logical-switch-augment";

        container lsw-attribute {
            config false;
            uses fabrictype:logical-switch;
        }
    }

    augment "/topo:network-topology/topo:topology/topo:node" {
        description "Augmentation for logical router nodes provided by faas.";

        ext:augment-identifier "logical-router-augment";

        container lr-attribute {
            config false;
            uses fabrictype:logical-router;
        }
    }

    augment "/topo:network-topology/topo:topology/topo:node/topo:termination-point" {
        description "Augmentation for logical port provided by faas.";

        ext:augment-identifier "logical-port-augment";

        container lport-attribute {
            config false;
            uses fabrictype:logical-port;
        }
    }

    /**************servic api*******************/
    rpc create-logical-switch {
        input {
            leaf fabric-id {
                type fabric:fabric-id;
            }
            leaf name {
                type string;
            }
            leaf vni {
                description "virtual network identifier.usually it is allocated by fabric itself. ";
                type int32;
            }
            leaf external {
                type boolean;
                default false;
            }
        }
        output {
            leaf node-id {
                type topo:node-id;
            }
            uses fabrictype:logical-switch;
        }
    }

    rpc rm-logical-switch {
        input {
            leaf fabric-id {
                type fabric:fabric-id;
            }
            leaf node-id {
                type topo:node-id;
            }
        }
    }

    rpc create-logical-router {
        input {
            leaf fabric-id {
                type fabric:fabric-id;
            }
            leaf name {
                type string;
            }
        }
        output {
            leaf node-id {
                type topo:node-id;
            }
            uses fabrictype:logical-router;
        }
    }

    rpc rm-logical-router {
        input {
            leaf fabric-id {
                type fabric:fabric-id;
            }
            leaf node-id {
                type topo:node-id;
            }
        }
    }

    rpc add-static-route {
        input {
            leaf fabric-id {
                type fabric:fabric-id;
            }
            leaf node-id {
                type topo:node-id;
            }
            uses fabrictype:route-group;
        }
    }

    rpc rm-static-route {
        input {
            leaf fabric-id {
                type fabric:fabric-id;
            }
            leaf node-id {
                type topo:node-id;
            }
            leaf-list destination-prefix {
                type inet:ipv4-prefix;
            }
        }
    }

    rpc clear-static-route {
        input {
            leaf fabric-id {
                type fabric:fabric-id;
            }
            leaf node-id {
                type topo:node-id;
            }
        }
    }

    rpc create-logical-port {
        input {
            leaf fabric-id {
                type fabric:fabric-id;
            }
            leaf name {
                type string;
            }
            leaf logical-device {
                type topo:node-id;
            }
            container attribute {
                uses fabrictype:logical-port;
            }
        }
        output {
            leaf tp-id {
                type topo:tp-id;
            }
            uses fabrictype:logical-port;
        }
    }

    rpc rm-logical-port {
        input {
            leaf fabric-id {
                type fabric:fabric-id;
            }
            leaf logical-device {
                type topo:node-id;
            }
            leaf tp-id {
                type topo:tp-id;
            }
        }
    }

    rpc create-gateway {
        input {
            leaf fabric-id {
                type fabric:fabric-id;
            }
            leaf ip-address {
                type inet:ip-address;
            }
            leaf network {
                type inet:ip-prefix;
            }
            leaf logical-router {
                type topo:node-id;
            }
            leaf logical-switch {
                type topo:node-id;
            }
        }
        output {
            leaf tp-id {
                type topo:tp-id;
            }
            uses fabrictype:logical-port;
        }
    }

    rpc rm-gateway {
        input {
            leaf fabric-id {
                type fabric:fabric-id;
            }
            leaf ip-address {
                type inet:ip-address;
            }
            leaf logical-router {
                type topo:node-id;
            }
        }
    }

    rpc port-binding-logical-to-fabric {
        input {
            leaf fabric-id {
                type fabric:fabric-id;
            }
            leaf logical-device {
                type topo:node-id;
            }
            leaf logical-port {
                type topo:tp-id;
            }
            leaf fabric-port {
                type topo:tp-id;
            }
        }
    }

    rpc port-binding-logical-to-device {
        input {
            leaf fabric-id {
                type fabric:fabric-id;
            }
            leaf logical-device {
                type topo:node-id;
            }
            leaf logical-port {
                type topo:tp-id;
            }
            leaf physical-port {
                type fabrictype:tp-ref;
            }
        }
    }

    rpc add-port-function {
        input {
            leaf fabric-id {
                type fabric:fabric-id;
            }
            leaf logical-device {
                type topo:node-id;
            }
            leaf logical-port {
                type topo:tp-id;
            }
            uses fabrictype:port-functions;
        }
    }

    rpc add-acl {
        input {
            leaf fabric-id {
                type fabric:fabric-id;
            }
            leaf logical-device {
                type topo:node-id;
            }
            leaf logical-port {
                type topo:tp-id;
            }
            leaf acl-name {
                type string;
            }
        }
    }

    rpc del-acl {
        input {
            leaf fabric-id {
                type fabric:fabric-id;
            }
            leaf logical-device {
                type topo:node-id;
            }
            leaf logical-port {
                type topo:tp-id;
            }
            leaf acl-name {
                type string;
            }
        }
    }
}
