module fabric-capable-device {

    yang-version 1;
    namespace "urn:opendaylight:faas:fabric:capable:device";
    prefix fabric-device;

    import ietf-inet-types { prefix "inet"; revision-date "2013-07-15"; }
    import network-topology { prefix "topo"; revision-date "2013-10-21"; }
    import ietf-yang-types { prefix "yang"; revision-date "2013-07-15"; }
    import yang-ext { prefix "ext"; revision-date "2013-07-09"; }
    import fabric-types { prefix fabrictype; revision-date "2015-09-30"; }
    import ietf-access-control-list { prefix acl; revision-date "2016-02-18"; }

    description
        "This module contains a collection of YANG definitions for Fabric.";

    revision "2015-09-30" {
        description
            "Initial revision of faas.";
    }

    identity fabric-capable-device-context {
    }

    grouping fabric-capable-device-attribute {
        leaf fabric-id {
            type topo:node-id;
        }
        leaf fabric-ref {
            type fabrictype:node-ref;
        }
    }

    grouping fabric-capable-device-config {
        list bridge-domain {
            key id;
            leaf id {
                type string;
            }
            leaf flood {
                type boolean;
                default false;
            }
            leaf arp {
                type boolean;
                default false;
            }
            leaf segment {
          		type uint32;
            }
        }

        list bd-port {
            key bd-port-id;
            leaf bd-port-id {
                type string;
            }
            leaf bdid {
                type string;
            }
            leaf ref-tp-id {
                type topo:tp-id;
            }
            leaf access-type {
                type fabrictype:access-type;
            }
            leaf access-tag {
                type uint32;
            }
            uses fabrictype:acl-list; 
        }

        list vrf {
            key id;
            leaf id {
                type string;
            }
            leaf name {
                type string;
            }
            leaf vrf-ctx {
                type int32;
            }
        }

        list bdif {
            key id;
            leaf id {
                type string;
            }
            leaf bdid {
                type string;
            }
            leaf vrf {
                type int32;
            }
            leaf ip-address {
                type inet:ip-address;
            }
            leaf mask {
                type int32;
            }
            leaf mac-address {
                type yang:mac-address;
            }
            uses fabrictype:acl-list;
            uses fabrictype:port-functions;
        }
    }

    augment "/topo:network-topology/topo:topology/topo:node" {
        ext:augment-identifier "fabric-capable-device";
        ext:context-instance "fabric-context";

        leaf-list supported-fabric {
            type identityref {
                base fabrictype:fabric-type;
            }
        }

        leaf-list capability-supported {
			type fabrictype:service-capabilities;
        }

        container attributes {
            config false;
            uses fabric-capable-device-attribute;
        }

        container config {
            uses fabric-capable-device-config;
        }
    }

    augment "/topo:network-topology/topo:topology/topo:node/topo:termination-point" {
        ext:augment-identifier "fabric-port-aug";
        leaf port-role {
            type fabrictype:fabric-port-role;
        }
        leaf port-ref {
            type fabrictype:tp-ref;
        }
    }

    augment "/topo:network-topology/topo:topology/topo:node/topo:termination-point" {
        ext:augment-identifier "bridge-domain-port";

        leaf-list bd-ids {
            type instance-identifier;
        } 
    }
}
