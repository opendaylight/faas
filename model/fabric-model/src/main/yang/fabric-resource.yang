module fabric-resources {

    yang-version 1;
    namespace "urn:opendaylight:faas:fabric:resources";
    prefix fabric-services;

    import network-topology { prefix "topo"; revision-date "2013-10-21"; }
    import ietf-inet-types { prefix "inet"; revision-date "2013-07-15"; }
    import yang-ext { prefix "ext"; revision-date "2013-07-09"; }
    import fabric-types { prefix fabrictype; revision-date "2015-09-30"; }
    import fabric { prefix fabric; revision-date "2015-09-30"; }
    import ietf-access-control-list { prefix acl; revision-date "2016-02-18"; }


    revision "2016-05-30" {
        description
            "Initial revision of faas.";
    }

    rpc create-fabric-port {
    	description "Administrator can use this RPC to create a new fabric port, for example a tunnel port.";
        input {
            leaf fabric-id {
                type fabric:fabric-id;
            }
            container fabric-port {
                uses fabrictype:fabric-port;
            }
            leaf underlayer-port {
                type topo:tp-id;
            }
        }
    }

    rpc add-fabric-link {
        description "Sometimes the link of fabrics can not be discovered automatically,
        administrator can use this RPC to add link information manually. ";

        input {
            leaf source-fabric {
                type fabric:fabric-id;
            }
            leaf source-fabric-port {
                type topo:tp-id;
            }
            leaf dest-fabric {
                type fabric:fabric-id; 
            }
            leaf dest-fabric-port {
                type topo:tp-id;
            }
        }
        output {
        	leaf link-id {
        		type topo:link-id;
        	}
        }
    }

	rpc set-fabric-port-role {
		description "Administrator can use this RPC to set role of physical port according whole network design.";

        input {
            leaf fabric-id {
                type fabric:fabric-id;
            }
            leaf fabric-port-id {
                type topo:tp-id;
            }
            leaf port-role {
                type fabrictype:fabric-port-role;
            }
        }
	}
}
