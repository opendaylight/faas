module fabric {

    yang-version 1;
    namespace "urn:opendaylight:faas:fabric";
    prefix fabric;

    import network-topology { prefix "topo"; revision-date "2013-10-21"; }
    import yang-ext { prefix "ext"; revision-date "2013-07-09"; }
    import fabric-types { prefix "fabrictype"; revision-date "2015-09-30"; }

    description
        "This module contains a collection of YANG definitions for Fabric.";

    revision "2015-09-30" {
        description
            "Initial revision of faas.";
    }

    identity fabric-context {
    }

    typedef fabric-id {
        type topo:node-id;
        description
            "An identifier for a fabric in a topology.
            The identifier is generated by compose-fabric RPC.";
    }

    typedef port-id {
        type fabrictype:tp-ref;
        description
            "An identifier for a fabric in a topology.
            The identifier is generated by compose-fabric RPC.";
    }


    grouping fabric-options {
        leaf gateway-mode {
            type enumeration {
                enum centralized {
                    description "";
                }
                enum distributed {
                    description "";
                }
            }
            default "distributed";
        }

        leaf traffic-behavior {
            type enumeration {
                enum normal {
                    description "";
                }
                enum policy-driven {
                    description "";
                }
            }
            default "normal";
        }

        leaf-list capability-supported {
            type fabrictype:service-capabilities;
        }
    }

    grouping device-attributes {
        leaf device-ref {
            type fabrictype:node-ref;
        }
        leaf role {
            type fabrictype:device-role;
            default "LEAF";
        }
    }

    grouping link-attributes {
        leaf link-ref {
            type fabrictype:link-ref;
        }
    }

    grouping port-attributes {
        leaf port-ref {
            type fabrictype:tp-ref;
        }
        leaf port-type {
            type enumeration {
                enum ETH;
                enum SERIAL;
            }
        }
        leaf bandwith {
            type enumeration {
                enum 1G;
                enum 10G;
                enum 40G;
                enum 100G;
                enum 10M;
                enum 100M;
                enum 1M;
            }
        }
    }

    grouping fabric-attributes {
        
        leaf parent {
            type string;
            description "The name of the fabric directly contains current fabric";
        }
        
        leaf name {
            type string;
        }

        leaf type {
            type fabrictype:underlayer-network-type;
            description "The type of physical network that implements this fabric.
                        Examples are vlan, and trill.";
        }

        container vni-capacity {
            description "number of vnis the fabric has";
            leaf min {
                type int32;
            }

            leaf max {
                type int32;
            }
        }

        leaf description {
            type string;
        }

        container options {
            uses fabric-options;
        }

        list device-nodes {
            key device-ref;
            uses device-attributes;
        }

        list device-links {
            key link-ref;
            uses link-attributes;
        }

        list device-ports {
            key port-ref;
            uses port-attributes;
        }



    }

    augment "/topo:network-topology/topo:topology/topo:node" {
        description "Augmentation for fabric nodes created by faas.";

        ext:augment-identifier "fabric-node";
        ext:context-instance "fabric-context";

        container fabric-attribute {
            uses fabric-attributes;
        }
    }

    augment "/topo:network-topology/topo:topology/topo:node/topo:termination-point" {
        description "Augmentation for port on fabric.";

        ext:augment-identifier "fabric-port-augment";

        container fport-attribute {
            config false;
            uses fabrictype:fabric-port;
        }
    }

    /*******************************RPC*********************************************/
    rpc get-all-fabrics {
        output {
            leaf-list fabric-id {
               type fabric-id;
            }
        }
    }

    rpc compose-fabric {
        input {
            uses fabric-attributes;
        }
        output {
            leaf fabric-id {
                type fabric-id;
            }
        }
    }

    rpc decompose-fabric {
        input {
            leaf fabric-id {
                type fabric-id;
            }
        }
    }

    rpc add-node-to-fabric {
        input {
            leaf fabric-id {
                type fabric-id;
            }
            leaf node-ref {
                type fabrictype:node-ref;
            }
            leaf role {
                type fabrictype:device-role;
            }
        }
    }

    rpc rm-node-from-fabric {
        input {
            leaf fabric-id {
                type fabric-id;
            }
            leaf node-ref {
                type fabrictype:node-ref;
            }
        }
    }

    rpc add-link-to-fabric {
        input {
            leaf fabric-id {
                type fabric-id;
            }
            leaf link-ref {
                type fabrictype:link-ref;
            }
        }
    }

    rpc rm-link-from-fabric {
        input {
            leaf fabric-id {
                type fabric-id;
            }
            leaf link-ref {
                type fabrictype:link-ref;
            }
        }
    }

    rpc get-ports-from-fabric {
        input {
            leaf fabric-id {
                type fabric-id;
            }
        }
        output {
            leaf-list port-id {
               type port-id;
            }
        }
    }
}
