module vlan-fabric-impl {

    yang-version 1;
    namespace "urn:opendaylight:params:xml:ns:yang:controller:config:fabric:vlan:impl";
    prefix "vlan-fabric-impl";

    import ietf-yang-types { prefix "yang"; revision-date "2013-07-15"; }

    revision "2016-06-15" {
        description "initial revision.";
    }

    container vlan-fabric-config {
        list gateway-mac {
            leaf mac-address {
                type yang:mac-address;
            }
        }
    }
}
