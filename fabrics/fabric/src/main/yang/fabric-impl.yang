module fabric-impl {

    yang-version 1;
    namespace "urn:opendaylight:params:xml:ns:yang:controller:config:fabric:impl";
    prefix "fabric-impl";

    revision "2015-09-30" {
        description "initial revision.";
    }

    container fabrics-setting {
        leaf next-fabric-num {
            type uint32;
            default 1;
        }
    }
}
