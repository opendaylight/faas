module vxlan-fabric-impl {

    yang-version 1;
    namespace "urn:opendaylight:params:xml:ns:yang:controller:config:fabric:vxlan:impl";
    prefix "vxlan-fabric-impl";

    import ietf-yang-types { prefix "yang"; revision-date "2013-07-15"; }

    revision "2015-09-30" {
        description "initial revision.";
    }

    container vxlan-fabric-config {
        list gateway-mac {
            leaf mac-address {
                type yang:mac-address;
            }
        }
    }
}
