module vxlan-fabric-ce-netconf-adapter-impl {

    yang-version 1;
    namespace "urn:opendaylight:params:xml:ns:yang:controller:config:vxlan-fabric-ce-netconf-adapter:impl";
    prefix "ce-netconf-adapter-impl";

    import config { prefix config; revision-date 2013-04-05; }
    import opendaylight-md-sal-binding { prefix mdsal; revision-date 2013-10-28; }

    revision "2017-03-16" {
        description "initial revision.";
    }

    // This is the definition of the service implementation as a module identity.
    identity vxlan-fabric-ce-netconf-adapter-impl {
        base config:module-type;

        // Specifies the prefix for generated java classes.
        config:java-name-prefix VxlanFabricCENetconfAdapter;
    }

    // Augment the 'configuration' choice node under modules/module.
    augment "/config:modules/config:module/config:configuration" {
        case vxlan-fabric-ce-netconf-adapter-impl {
            when "/config:modules/config:module/config:type = 'vxlan-fabric-ce-netconf-adapter-impl'";

            container data-broker {
                uses config:service-ref {
                    refine type {
                        mandatory true;
                        config:required-identity mdsal:binding-async-data-broker;
                    }
                }
            }

            container rpc-registry {
                uses config:service-ref {
                    refine type {
                        mandatory true;
                        config:required-identity mdsal:binding-rpc-registry;
                    }
                }
            }

            container notification-service {
                uses config:service-ref {
                    refine type {
                        mandatory true;
                        config:required-identity mdsal:binding-notification-service;
                    }
                }
            }
        }
    }
}
