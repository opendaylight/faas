/**
 * Copyright (c) 2015 Huawei Technologies Co. Ltd. and others. All rights reserved.
 *
 * This program and the accompanying materials are made available under the
 * terms of the Eclipse Public License v1.0 which accompanies this distribution,
 * and is available at http://www.eclipse.org/legal/epl-v10.html
 */
module vc-ld-node {
    yang-version 1;
    namespace "urn:opendaylight:faas:vcontainer:ldnode";
    prefix "ld-node";

    import yang-ext { prefix ext; revision-date "2013-07-09"; }
    import network-topology { prefix "nt"; revision-date "2013-10-21"; }
    import ietf-yang-types { prefix "yang"; revision-date "2013-07-15"; }
    import vfabric { prefix vfabric; revision-date "2015-10-10"; }
    import appliance { prefix appliance; revision-date "2015-10-10"; }
    import vcontainer-types { prefix vctype; revision-date "2015-10-10"; }
    import vcontainer-topology { prefix vct; revision-date "2015-10-10"; }

    description
        "This module defines the LD node in the Virtual Container.";

    revision 2015-10-10 {
        description
                "Initial revision.";
    }

    /******************************* AUGMENT ***********************************/

    augment "/nt:network-topology/nt:topology/nt:node/vct:vc-node-attributes" {
        when "../../nt:topology-types/vct:vcontainer-topology";
        ext:augment-identifier "vc-ld-node";
        ext:context-instance "vc-ld-node-context";
        description "Augmentation for LD nodes";
        container ld-node-attributes {
            uses vctype:vc-ld-node-attributes;
        }
    }

    augment "/nt:network-topology/nt:topology/nt:node/nt:termination-point/vct:vc-termination-point-attributes" {
        when "../../../nt:topology-types/vct:vcontainer-topology";
        leaf ld-node-port-type {
            type vctype:vc-ld-node-port-type;
        }
    }

    /******************************* RPC ***********************************/

    rpc create-child-ld-node {
        input {
            leaf tenant-id {
                type vctype:tenant-id;
            }
            leaf parent-ld-node-id {
                type vctype:vc-ld-node-id;
            }
            container child-vcontainer-config {
                uses vctype:vc-ld-node-attributes;
            }
        }
        output {
            leaf child-ld-node-id {
                type vctype:vc-ld-node-id;
            }
        }
    }

    rpc removed-child-ld-node {
        input {
            leaf tenant-id {
                type vctype:tenant-id;
            }
            leaf child-ld-node-ref {
                type vctype:vc-ld-node-ref;
            }
        }
    }

    rpc add-vfabric-to-ld-node {
        input {
            leaf tenant-id {
                type vctype:tenant-id;
            }
            leaf ld-node-id {
                type vctype:vc-ld-node-id;
            }
            leaf vfabric-id {
                type vctype:vfabric-id;
            }
        }
    }

    rpc rm-vfabric-from-ld-node {
        input {
            leaf tenant-id {
                type vctype:tenant-id;
            }
            leaf ld-node-id {
                type vctype:vc-ld-node-id;
            }
            leaf vfabric-id {
                type vctype:vfabric-id;
            }
        }
    }

    rpc add-appliance-to-ld-node {
        input {
            leaf tenant-id {
                type vctype:tenant-id;
            }
            leaf ld-node-id {
                type vctype:vc-ld-node-id;
            }
            leaf appliance-id {
                type vctype:appliance-id;
            }
        }
    }

    rpc rm-appliance-from-ld-node {
        input {
            leaf tenant-id {
                type vctype:tenant-id;
            }
            leaf ld-node-id {
                type vctype:vc-ld-node-id;
            }
            leaf appliance-id {
                type vctype:appliance-id;
            }
        }
    }
}
