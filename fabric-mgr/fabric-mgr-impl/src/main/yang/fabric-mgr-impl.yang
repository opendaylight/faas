/**
 * Copyright (c) 2015 Huawei Technologies Co. Ltd. and others. All rights reserved.
 *
 * This program and the accompanying materials are made available under the
 * terms of the Eclipse Public License v1.0 which accompanies this distribution,
 * and is available at http://www.eclipse.org/legal/epl-v10.html
 */
module fabric-mgr-impl {

    yang-version 1;
    namespace "urn:opendaylight:params:xml:ns:yang:controller:config:fabric-mgr:impl";
    prefix "fabric-mgr-impl";

    import config { prefix config; revision-date 2013-04-05; }
    import opendaylight-md-sal-binding { prefix mdsal; revision-date 2013-10-28; }
    import opendaylight-sal-binding-broker-impl { prefix sal-broker; revision-date 2013-10-28; }

    revision "2015-11-09" {
        description "initial revision.";
    }

    // This is the definition of the service implementation as a module identity.
    identity fabric-mgr-impl {
        base config:module-type;

        // Specifies the prefix for generated java classes.
        config:java-name-prefix fabric-mgr;
    }

    // Augment the 'configuration' choice node under modules/module.
    augment "/config:modules/config:module/config:configuration" {
        case fabric-mgr-impl {
            when "/config:modules/config:module/config:type = 'fabric-mgr-impl'";

            container data-broker {
                uses config:service-ref {
                    refine type {
                        mandatory true;
                        config:required-identity mdsal:binding-async-data-broker;
                    }
                }
            }

            container rpc-registry {
                uses config:service-ref {
                    refine type {
                        mandatory true;
                        config:required-identity mdsal:binding-rpc-registry;
                    }
                }
            }

            container notification-adapter {
                uses config:service-ref {
                    refine type {
                        mandatory true;
                        config:required-identity sal-broker:binding-new-notification-service;
                    }
                }
            }
        }
    }
}
