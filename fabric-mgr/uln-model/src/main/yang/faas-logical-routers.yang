/*
 * Copyright (c) 2015 Huawei Technologies and others.  All rights reserved.
 *
 * This program and the accompanying materials are made available under the
 * terms of the Eclipse Public License v1.0 which accompanies this distribution,
 * and is available at http://www.eclipse.org/legal/epl-v10.html
 */
module faas-logical-routers {
    namespace "urn:opendaylight:faas:logical:faas-logical-routers";
    prefix "faas-logical-routers";

    import faas-common { prefix faas-common; }

    revision 2015-10-13 {
        description "Initial revision";
    }

    grouping logical-routers-container {
        container logical-routers {
            list logical-router {
                uses faas-common:admin-attributes;
                key "uuid";
                uses faas-common:logical-entity-attributes;
                leaf public {
                    description "True if there is at least one port accessed by the Internet";
                    type boolean;
                }
            }
        }
    }
}
