module vcontainer-types {

    yang-version 1;
    namespace "urn:opendaylight:faas:vcontainer:type";
    prefix vcontainer-types;

    import ietf-yang-types { prefix "yang"; revision-date "2013-07-15"; }
    import ietf-inet-types { prefix "inet"; revision-date "2010-09-24"; }
    import network-topology { prefix "topo"; revision-date "2013-10-21"; }

    description
        "This module contains a collection of YANG definitions for data
        types used for DC Fabric configuration. ";

    revision "2015-10-10" {
        description
                "Initial revision.";
    }

    identity vcontainer-types {
    }

    /******************* typedef **********************/

    typedef tenant-id {
        type yang:uuid;
        description "Owner ID of a vcontainer ";
    }
    
    typedef vcontainer-id {
        type yang:uuid;
        description "An identifier for a vcontainer.";
    }

    typedef vcontainer-ref {
        type leafref {
            path "/dc-container/vcontainer/vcontainer-id";
        }
    }
    
    typedef vfabric-id {
        type topo:node-id;
        description
            "An identifier for a vfabric in a vfabric-topology.
            The identifier is generated by create-vfabric RPC.";
    }
    
    typedef vfabric-ref {
        type topo:node-ref;
        description "Reference to a vfabric node";
    }
    
    typedef vfabric-port-id {
        type topo:tp-id;
        description "Id of a vfabric port";
    }
    
    typedef vfabric-port-ref {
        type topo:tp-ref;
        description "Reference to a port on a vfabric node";
    }

    typedef appliance-id {
        type topo:node-id;
        description
                "An identifier for an appliance";
    }
    
    typedef appliance-ref {
        type topo:node-ref;
        description "Reference to an appliance node";
    }
    
    typedef appliance-port-id {
        type topo:tp-id;
        description "ID of a port on an appliance node";
    }

    typedef appliance-port-ref {
        type topo:tp-ref;
        description "Reference to a port on an appliance node";
    }
    
    typedef vf-lsw-id {
        type topo:node-id;
        description "VFabric logical switch ID";
    }
    
    typedef vf-lsw-ref {
        type topo:node-ref;
        description "Reference to a logical switch on a vfabric node";
    }
    
    typedef vf-lr-id {
        type topo:node-id;
        description "VFabric logical router ID";
    }
    
    typedef vf-lr-ref {
        type topo:node-ref;
        description "Reference to a logical router on a vfabric node";
    }
    
    typedef device-role {
        description "device role type";
        type enumeration {
            enum SPINE {
                description "";
            }
            enum LEAF {
                description "";
            }
        }
    }

    typedef port-role {
        description "port role type";
        type enumeration {
            enum NNI {
                description "the port used for fabric intra communication.";
            }
            enum UNI {
                description "the port used for Endpoint to access fabric.";
            }
        }
    }

    typedef access-type {
        description "";
        type enumeration {
            enum exclusive;
            enum vlan;
        }
    }

    typedef logical-connection-id {
        type topo:link-id;
    }
    
    typedef logical-connection-ref {
        type topo:link-ref;
    }
    
    typedef logical-connection-type {
        description "connection type";
        type enumeration {
            enum VLAN_TUNNEL {
                description "layer 2 tunnel using vlan";
            }
            enum VXLAN_TUNNEL {
                description "layer 2 tunnel using vxlan overlay";
            }
            enum L3_VRF_CONNECTION {
                description "layer 3 tunnel that connects 2 VRFs that belong to one vpn instance";
            }
            enum LSW_LR_CONNECTION {
                description "connection between a logical switch and a logical router";
            }
            enum SFC_CONNECTION {
                description "connection between a logical device (lsw or lr) and an appliance";
            }
        }
    }
    
    typedef vc-ld-id {
        type topo:node-id;
        description "Vcontainer Logical Device (LD) ID";
    }
    
    typedef vc-ld-ref {
        type topo:node-ref;
        description "Reference to a LD node";
    }
    
    /******************* Grouping **********************/
    /*
    grouping vc-port-attributes {
        leaf vfabric {
            mandatory true;
            type vfabric-ref;
        }
        leaf tp {
            type topo:tp-ref;
        }
    }

    grouping vc-io-port-attributes {
    	uses vc-port-attributes;
    }

    grouping vc-ld-attributes {
    	leaf vc-ref {
    		type vcontainer-ref; 
    		description "reference to the corresponding vcontainer";
    	}
    	list io-ports {
    		uses vc-io-port-attributes;
    	}
    }

    grouping l2-resource-range {
    	leaf low-id {
    		type int32;
    	}
    	leaf high-id {
    		type int32;
    	}
    }

    grouping l3-resource-range {
    	leaf low-ip-addr {
    		type inet:ip-address;
    	}
    	leaf high-ip-addr {
    		type inet:ip-address;
    	}
    }

    grouping routing-table-entry {
    	leaf dest-ip {
    		type inet:ip-address;
    	}
    	leaf nexthop-ip {
    		type inet:ip-address;
    	}
    	leaf vrf-id {
    		type string;
    	}
    }

    grouping vf-lsw-attributes {
        leaf lsw-uuid {
            type yang:uuid;
        }
        leaf name {
            type string;
        }
        leaf segment-id {
            type uint32;
        }
    }
    
    grouping vf-lr-attributes {
        leaf lr-uuid {
            type yang:uuid;
        }
        leaf name {
            type string;
        }
        leaf vrf-ctx {
            type uint32;
        }
        list routing-table {
        	key "dest-ip";
        	uses routing-table-entry;
        }
    }

    grouping logical-connection-attributes {
    	leaf connection-type {
    		type logical-connection-type;
    	}
   		//TODO 	
    }

    grouping logical-port-attributes {
    	leaf port-role {
    		type port-role;
    	}
    	leaf reference-couner {
    		type uint32;
    		description "Reference counter to denote number of users using the port. 
    					 The port is free when the counter becomes zero.
    					 This concept is similiar to the ref counter in the 
    					 inode of the Unix file system.";
    	}
        container layer-1-info {
            leaf location {
                type topo:tp-ref;
            }
        }
        container layer-2-info {
            leaf access-type {
                type access-type;
            }
            leaf access-seqment {
                type uint32;
            }
        }
        container layer-3-info {
            leaf ip {
                type inet:ip-address;
            }
            leaf mac {
                type yang:phys-address;
            }
            leaf forward-enable {
                type boolean;
            }
        }
    }
    */
 }
